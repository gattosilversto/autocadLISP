(defun c:z ( / p1 p2 XtoY Ytox VsMax VsMin X Y rm bm ex Pad Tiny)
 (setq rm (getvar "regenmode")
       bm (getvar "blipmode")
       ex (getvar "expert"))
 (setvar "expert" 0)
 (setvar "cmdecho" 0)
 (setvar "regenmode" 0)
 (initget 1 "Max Window Previous Tiny")
 (setq p1 (getkword "\nPrevious/Max/Tiny/Window: ")
       VsMax (getvar "vsmax")
       VsMin (getvar "vsmin")
       Pad (* (- (car VsMax)(car VsMin)) 0.0001)
       Tiny (/ (- (cadr VsMax)(cadr VsMin))
           (- (fix (/ 32767 (apply 'max (getvar "screensize")))) 0.00001)))
 (command ".zoom")
   (cond ((= p1 "Window")
     (setq p1 (getpoint "\nFirst corner: ")
           p2 (getcorner p1 "\nOther corner: ")
           X (abs (- (car p1)(car p2)))
           Y (abs (- (cadr p1)(cadr p2)))
           XtoY (/ (- (car VsMax)(car VsMin))(- (cadr VsMax)(cadr VsMin)))
           YtoX (/ (- (cadr VsMax)(cadr VsMin))(- (car VsMax)(car VsMin))))
     (if (< X (* XtoY Y))
        (setq X (* Y XtoY))
        (setq Y (* X YtoX)))
     (setvar "blipmode" 0)
     (if (> Y Tiny)
       (progn
         (setq p1 (mapcar 'min p1 p2)
               p2 (mapcar '- (mapcar 'min
                                 (list (+ (car p1) X)(+ (cadr p1) Y)) VsMax)
                      (list Pad Pad))
               p1 (mapcar '+ (mapcar 'max (mapcar '- p2 (list X Y)) VsMin)
                      (list Pad Pad)))
         (command "w" p1 p2))
       (progn
         (princ "\nZoom would cause a regeneration. Zooming Tiny instead. ")
         (command "c" p1 Tiny))))
   ((= p1 "Previous")(command "p"))
   ((= p1 "Tiny")
     (initget 9)
     (setq p1 (getpoint "\nCenter point: "))
     (command "c" p1 Tiny))
   ((= p1 "Max")
     (command "w" (mapcar '+ VsMin (list Pad Pad))
              (mapcar '- VsMax (list Pad Pad)))))
 (setvar "expert" ex)
 (setvar "blipmode" bm)
 (setvar "regenmode" rm)(princ)
);z
